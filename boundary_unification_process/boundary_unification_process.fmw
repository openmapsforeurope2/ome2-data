FME workspace boundary_unification_process.fmw

Parameters:
- SourceDataset_POSTGIS = be_national   # Database country 1
- SourceDataset_POSTGIS_4 = nl_national   # Database country 2
- DestDataset_POSTGIS_2 = ome2_v0   # Destination database (write)
- SourceDataset_POSTGIS_6 = ome2_v0   # Destination database (read)

Readers:
- POSTGIS_2: POSTGIS from $(SourceDataset_POSTGIS)
- POSTGIS_3: POSTGIS from $(SourceDataset_POSTGIS_4)
- POSTGIS_5: POSTGIS from $(SourceDataset_POSTGIS_6)

Writers:
- POSTGIS_4: POSTGIS to $(DestDataset_POSTGIS_2)

Bookmark: Step 1.1: Extract outer international boundaries from administrative units
top10nl_registratief_gebied_multivlak (reader POSTGIS_3) [off]
    attributes: id serial,PrimaryKey, namespace varchar(200), lokaalid varchar(160), brontype varchar(240), bronactualiteit date, bronbeschrijving varchar(960), bronnauwkeurigheid float8, mutatietype varchar(256), typeregistratiefgebied varchar(16), naamofficieel varchar(1016), naamnl varchar(1024), naamfries varchar(1024), nummer varchar(1024), objectbegintijd date, tijdstipregistratie date, visualisatiecode int8, tdncode int8
    -> Reprojector
Reprojector
    DEST = LL-WGS84
    INTERPOLATION_TYPE_NAME = Nearest Neighbor
    RASTER_CELL_SIZE = Preserve Cells
    RASTER_TOLERANCE = 0.0
    REPROJECTED -> Dissolver_2
Dissolver_2
    ACCUM_INPUT_ATTRS = Use Attributes From One Feature
    CLEANING_TOLERANCE = Automatic
    CONNECT_Z_MODE = First Wins
    DEAGGREGATE_INPUT = Yes
    AREA -> TopologyBuilder_2
TopologyBuilder_2
    ALLOW_CYCLES = No
    BOUNDING_EDGES = All
    CLEANING_TOLERANCE = Automatic
    DEAGGREGATE_INPUT = Yes
    GENERATION_MODE = INTERSECT
    MAX = 0
    OVERLAPPING_MODE = No
    LINE -> Intersector_2
municipality (reader POSTGIS_2) [off]
    attributes: fid serial,PrimaryKey, tgid varchar(38), modifdate timestamptz, arrondissementcapital bool, provincecapital bool, regioncapital bool, countrycapital bool, niscode varchar(255), city int4, languagestatute int4, nameger varchar(80), namefre varchar(80), namedut varchar(80)
    -> Dissolver
Dissolver
    ACCUM_INPUT_ATTRS = Use Attributes From One Feature
    CLEANING_TOLERANCE = Automatic
    CONNECT_Z_MODE = First Wins
    DEAGGREGATE_INPUT = Yes
    AREA -> TopologyBuilder
TopologyBuilder
    ALLOW_CYCLES = No
    BOUNDING_EDGES = All
    CLEANING_TOLERANCE = Automatic
    DEAGGREGATE_INPUT = Yes
    GENERATION_MODE = INTERSECT
    MAX = 0
    OVERLAPPING_MODE = No
    LINE -> Intersector_2
Intersector_2
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> LineCombiner_4
LineCombiner_4
    ACCUM_ATTRS_NAME = Use Attributes From One Feature
    BREAK = no
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> _INTBND1_lines (writer POSTGIS_4)
    LINE -> _INTBND1_lines_corrected (writer POSTGIS_4)
_INTBND1_lines (writer POSTGIS_4)
    attributes: fid serial,PrimaryKey, tgid varchar(38), modifdate timestamptz, arrondissementcapital bool, provincecapital bool, regioncapital bool, countrycapital bool, niscode varchar(255), city int4, languagestatute int4, nameger varchar(80), namefre varchar(80), namedut varchar(80), _edge_id int8, _right_face int8, _left_face int8, _right_edge int8, _left_edge int8, _from_node int8, _to_node int8, _faces int8, id serial,PrimaryKey, namespace varchar(200), lokaalid varchar(160), brontype varchar(240), bronactualiteit date, bronbeschrijving varchar(960), bronnauwkeurigheid float8, mutatietype varchar(256), typeregistratiefgebied varchar(16),
      naamofficieel varchar(1016), naamnl varchar(1024), naamfries varchar(1024), nummer varchar(1024), objectbegintijd date, tijdstipregistratie date, visualisatiecode int8, tdncode int8, _overlaps int8, _segments int8
_INTBND1_lines_corrected (writer POSTGIS_4)
    attributes: fid serial,PrimaryKey, tgid varchar(38), modifdate timestamptz, arrondissementcapital bool, provincecapital bool, regioncapital bool, countrycapital bool, niscode varchar(255), city int4, languagestatute int4, nameger varchar(80), namefre varchar(80), namedut varchar(80), _edge_id int8, _right_face int8, _left_face int8, _right_edge int8, _left_edge int8, _from_node int8, _to_node int8, _faces int8, id serial,PrimaryKey, namespace varchar(200), lokaalid varchar(160), brontype varchar(240), bronactualiteit date, bronbeschrijving varchar(960), bronnauwkeurigheid float8, mutatietype varchar(256), typeregistratiefgebied varchar(16),
      naamofficieel varchar(1016), naamnl varchar(1024), naamfries varchar(1024), nummer varchar(1024), objectbegintijd date, tijdstipregistratie date, visualisatiecode int8, tdncode int8, _overlaps int8, _segments int8

Bookmark: Step 3: Generate skeletons from the boundary polygons
_INTBND2_polygons_corrected (reader POSTGIS_5) [off]
    attributes: fid serial,PrimaryKey, tgid varchar(38), modifdate timestamptz, arrondissementcapital bool, provincecapital bool, regioncapital bool, countrycapital bool, niscode varchar(255), city int4, languagestatute int4, nameger varchar(80), namefre varchar(80), namedut varchar(80), _edge_id int8, _right_face int8, _left_face int8, _right_edge int8, _left_edge int8, _from_node int8, _to_node int8, _faces int8, id serial, namespace varchar(200), lokaalid varchar(160), brontype varchar(240), bronactualiteit date, bronbeschrijving varchar(960), bronnauwkeurigheid float8, mutatietype varchar(256), typeregistratiefgebied varchar(16),
      naamofficieel varchar(1016), naamnl varchar(1024), naamfries varchar(1024), nummer varchar(1024), objectbegintijd date, tijdstipregistratie date, visualisatiecode int8, tdncode int8, _overlaps int8, _segments int8
    -> CenterlineReplacer
CenterlineReplacer
    MODE = SKELETON
    CENTERLINE -> Intersector
Intersector
    ATTRS_ACCUM_MODE = Use Attributes From One Feature
    CLEANING_TOLERANCE = Automatic
    DEAGGREGATE_INPUT = Yes
    DIRECTION_NAME = _direction
    DUPLICATE_Z_NODES = No
    GENERATE_LIST_DROP = NO
    MEASURE_TYPE = Continuous
    NODE_NUM_ATTR = _node_number
    OV_ATTR = _overlaps
    SEG_ATTR = _segments
    SEPARATE_COLLINEAR_SEGMENTS = No
    INTERSECTED -> AttributeManager
AttributeManager
    ATTR_TABLE:
      REMOVE tgid
      REMOVE modifdate
      REMOVE arrondissementcapital
      REMOVE provincecapital
      REMOVE regioncapital
      REMOVE countrycapital
      REMOVE niscode
      REMOVE city
      REMOVE languagestatute
      REMOVE nameger
      REMOVE namefre
      REMOVE namedut
      REMOVE _edge_id
      REMOVE _right_face
      REMOVE _left_face
      REMOVE _right_edge
      REMOVE _left_edge
      REMOVE _from_node
      REMOVE _to_node
      REMOVE _faces
      REMOVE id
      REMOVE namespace
      REMOVE lokaalid
      REMOVE brontype
      REMOVE bronactualiteit
      REMOVE bronbeschrijving
      REMOVE bronnauwkeurigheid
      REMOVE mutatietype
      REMOVE typeregistratiefgebied
      REMOVE naamofficieel
      REMOVE naamnl
      REMOVE naamfries
      REMOVE nummer
      REMOVE objectbegintijd
      REMOVE tijdstipregistratie
      REMOVE visualisatiecode
      REMOVE tdncode
      REMOVE _overlaps
      REMOVE _segments
    -> AttributeCreator
AttributeCreator
    ATTR_TABLE:
      SET_TO country = BE#NL
      SET_TO national_level = 1st_order
      SET_TO legal_satus = not_agreed
      SET_TO technical_status = calculated
    -> _INTBND3_skeleton (writer POSTGIS_4)
_INTBND3_skeleton (writer POSTGIS_4)
    attributes: country varchar(200), national_level varchar(200), legal_satus varchar(200), technical_status varchar(200), fid serial,PrimaryKey

Bookmark: Step 4.1: Automatically delete irrelevant lines dangling from the main centerline
_INTBND1_lines_corrected (reader POSTGIS_5) [off]
    attributes: fid serial,PrimaryKey, tgid varchar(38), modifdate timestamptz, arrondissementcapital bool, provincecapital bool, regioncapital bool, countrycapital bool, niscode varchar(255), city int4, languagestatute int4, nameger varchar(80), namefre varchar(80), namedut varchar(80), _edge_id int8, _right_face int8, _left_face int8, _right_edge int8, _left_edge int8, _from_node int8, _to_node int8, _faces int8, id serial, namespace varchar(200), lokaalid varchar(160), brontype varchar(240), bronactualiteit date, bronbeschrijving varchar(960), bronnauwkeurigheid float8, mutatietype varchar(256), typeregistratiefgebied varchar(16),
      naamofficieel varchar(1016), naamnl varchar(1024), naamfries varchar(1024), nummer varchar(1024), objectbegintijd date, tijdstipregistratie date, visualisatiecode int8, tdncode int8, _overlaps int8, _segments int8
    -> LineCombiner
    -> AreaBuilder [off]
Note: Official boundary nodes table
ib_boundary_nodes (reader POSTGIS_5) [off]
    attributes: inspireid int4, country varchar(8), legal_status text, technical_status text
    -> SpatialFilter_3 [Filter]
_INTBND3_skeleton (reader POSTGIS_5) [off]
    attributes: country varchar(200), national_level varchar(200), legal_satus varchar(200), technical_status varchar(200), fid serial,PrimaryKey
    -> SpatialFilter_3 [Candidate]
    -> SpatialRelator [Requestor]
TopologyBuilder_3
    ALLOW_CYCLES = No
    BOUNDING_EDGES = All
    CLEANING_TOLERANCE = Automatic
    DEAGGREGATE_INPUT = Yes
    GENERATION_MODE = INTERSECT
    MAX = 0
    OVERLAPPING_MODE = No
    NODE -> SpatialRelator_2 [Requestor]
SpatialRelator_2
    AGGREGATE_HANDLING = Yes
    CALC_CARD = No
    CURVE_BOUNDARY_RULE_PARAM = Default Rule
    LIST_NAME = _relationships
    PREDICATES = INTERSECTS TOUCHES
    SUCCESS_ATTR = _nb_of_suppliers
    -> Tester_2
Tester_2
    BOOL_OP = OR
    TEST_CLAUSE = TEST @Value(_nb_of_suppliers) = 1
    TEST_MODE = TEST
    PASSED -> SpatialFilter_4 [Candidate]
AreaBuilder_2
    ALLOW_CYCLES = No
    CHECK_CURVE_DIRECTION = No
    CONNECT_Z_MODE = First Wins
    CONSIDER_NODE_ELEVATION = no
    DEAGGREGATE_INPUT = Deaggregate
    DONUT_CREATION = Yes
    DROP_HOLES = No
    LINES_AS_SEGMENTS = No
    POLY_ACCUM_ATTRS_NAME = Use Attributes From One Feature
    SNAPTYPE_PARAM = None
    AREA -> SpatialFilter_4 [Filter]
SpatialFilter_4
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> SpatialFilter_2 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    FAILED -> LineCombiner_5
LineCombiner_5
    ACCUM_ATTRS_NAME = Use Attributes From One Feature
    BREAK = no
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> UUIDGenerator_2
UUIDGenerator_2
    UUID_ATTR = tmp_uuid_2
    -> AttributeManager_3
AttributeManager_3
    ATTR_TABLE = REMOVE tmp_uuid
    -> TopologyBuilder_5
    -> _INTBND4_corrected (writer POSTGIS_4)
    -> SpatialRelator_6 [Supplier]
_INTBND4_corrected (writer POSTGIS_4)
    attributes: country varchar(200), national_level varchar(200), legal_satus varchar(200), technical_status varchar(200), tmp_uuid_2 text,PrimaryKey
TopologyBuilder_5
    ALLOW_CYCLES = No
    BOUNDING_EDGES = All
    CLEANING_TOLERANCE = Automatic
    DEAGGREGATE_INPUT = Yes
    GENERATION_MODE = INTERSECT
    MAX = 0
    OVERLAPPING_MODE = No
    NODE -> SpatialRelator_6 [Requestor]
SpatialRelator_6
    AGGREGATE_HANDLING = Yes
    CALC_CARD = No
    CURVE_BOUNDARY_RULE_PARAM = Default Rule
    LIST_NAME = _relationships
    PREDICATES = INTERSECTS TOUCHES
    SUCCESS_ATTR = _nb_of_suppliers
    -> Tester_4
Tester_4
    BOOL_OP = OR
    TEST_CLAUSE = TEST @Value(_nb_of_suppliers) >= 3
    TEST_MODE = TEST
    PASSED -> _INTBND4_suspicious_nodes (writer POSTGIS_4)
_INTBND4_suspicious_nodes (writer POSTGIS_4)
    attributes: country varchar(200), national_level varchar(200), legal_satus varchar(200), technical_status varchar(200), tmp_uuid_2 text, _node_number int8,PrimaryKey, _nb_of_suppliers int8

Bookmark: Step 2.1: Create polygons where the two initial boundaries are different
AreaBuilder
    ALLOW_CYCLES = No
    CHECK_CURVE_DIRECTION = No
    CONNECT_Z_MODE = First Wins
    CONSIDER_NODE_ELEVATION = no
    DEAGGREGATE_INPUT = Deaggregate
    DONUT_CREATION = YES
    DROP_HOLES = No
    LINES_AS_SEGMENTS = No
    POLY_ACCUM_ATTRS_NAME = Use Attributes From One Feature
    SNAPTYPE_PARAM = None
    AREA -> _INTBND2_polygons (writer POSTGIS_4)
    AREA -> _INTBND2_polygons_corrected (writer POSTGIS_4)
_INTBND2_polygons (writer POSTGIS_4)
    attributes: fid serial,PrimaryKey, tgid varchar(38), modifdate timestamptz, arrondissementcapital bool, provincecapital bool, regioncapital bool, countrycapital bool, niscode varchar(255), city int4, languagestatute int4, nameger varchar(80), namefre varchar(80), namedut varchar(80), _edge_id int8, _right_face int8, _left_face int8, _right_edge int8, _left_edge int8, _from_node int8, _to_node int8, _faces int8, id serial, namespace varchar(200), lokaalid varchar(160), brontype varchar(240), bronactualiteit date, bronbeschrijving varchar(960), bronnauwkeurigheid float8, mutatietype varchar(256), typeregistratiefgebied varchar(16),
      naamofficieel varchar(1016), naamnl varchar(1024), naamfries varchar(1024), nummer varchar(1024), objectbegintijd date, tijdstipregistratie date, visualisatiecode int8, tdncode int8, _overlaps int8, _segments int8
_INTBND2_polygons_corrected (writer POSTGIS_4)
    attributes: fid serial,PrimaryKey, tgid varchar(38), modifdate timestamptz, arrondissementcapital bool, provincecapital bool, regioncapital bool, countrycapital bool, niscode varchar(255), city int4, languagestatute int4, nameger varchar(80), namefre varchar(80), namedut varchar(80), _edge_id int8, _right_face int8, _left_face int8, _right_edge int8, _left_edge int8, _from_node int8, _to_node int8, _faces int8, id serial, namespace varchar(200), lokaalid varchar(160), brontype varchar(240), bronactualiteit date, bronbeschrijving varchar(960), bronnauwkeurigheid float8, mutatietype varchar(256), typeregistratiefgebied varchar(16),
      naamofficieel varchar(1016), naamnl varchar(1024), naamfries varchar(1024), nummer varchar(1024), objectbegintijd date, tijdstipregistratie date, visualisatiecode int8, tdncode int8, _overlaps int8, _segments int8

Bookmark: Initial selection
LineCombiner
    ACCUM_ATTRS_NAME = Use Attributes From One Feature
    BREAK = no
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> SpatialRelator [Supplier]
    LINE -> SpatialFilter [Filter]
LineCombiner_2
    ACCUM_ATTRS_NAME = Drop Incoming Attributes
    BREAK = no
    BREAK_CONNECTION_ATTRIBUTES = legal_satus national_level technical_status country
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> UUIDGenerator
UUIDGenerator
    UUID_ATTR = tmp_uuid
    -> SpatialFilter_2 [Candidate]
    -> TopologyBuilder_3
    -> SpatialRelator_2 [Supplier]
    -> AreaBuilder_2

Bookmark: Step 4.3: Finalization (line combining and UUIDs)
_INTBND4_corrected (reader POSTGIS_5)
    attributes: country varchar(200), national_level varchar(200), legal_satus varchar(200), technical_status varchar(200), tmp_uuid_2 text,PrimaryKey
    -> LineCombiner_3
    -> SpatialRelator_3 [Supplier]
LineCombiner_3
    ACCUM_ATTRS_NAME = Use Attributes From One Feature
    BREAK = no
    CONNECT_Z_MODE = First Wins
    CONSIDER_NODE_ELEVATION = no
    DEAGGREGATE_GEOMETRY = Deaggregate
    JUNCTIONS_IGNORE_ATTRIBUTES = No
    LINES_AS_SEGMENTS = No
    PRESERVE = no
    TOPOLOGY = End noded
    LINE -> UUIDGenerator_3
UUIDGenerator_3
    UUID_ATTR = inspireid
    -> _INTBND5_boundary_final (writer POSTGIS_4)
    -> TopologyBuilder_4
_INTBND5_boundary_final (writer POSTGIS_4)
    attributes: inspireid text,PrimaryKey, country varchar(200), national_level varchar(200), legal_satus varchar(200), technical_status varchar(200)
TopologyBuilder_4
    ALLOW_CYCLES = No
    BOUNDING_EDGES = All
    CLEANING_TOLERANCE = Automatic
    DEAGGREGATE_INPUT = Yes
    GENERATION_MODE = INTERSECT
    MAX = 0
    OVERLAPPING_MODE = No
    NODE -> SpatialRelator_3 [Requestor]
SpatialRelator_3
    AGGREGATE_HANDLING = Yes
    CALC_CARD = No
    CURVE_BOUNDARY_RULE_PARAM = Default Rule
    LIST_NAME = _relationships
    PREDICATES = INTERSECTS TOUCHES
    SUCCESS_ATTR = _nb_of_suppliers
    -> Tester_3
Tester_3
    BOOL_OP = OR
    TEST_CLAUSE = TEST @Value(_nb_of_suppliers) >= 3
    TEST_MODE = TEST
    PASSED -> _INTBND5_suspicious_nodes_verification (writer POSTGIS_4)
Note: There shouldn't be anymore suspicious nodes
_INTBND5_suspicious_nodes_verification (writer POSTGIS_4)
    attributes: country varchar(200), national_level varchar(200), legal_satus varchar(200), technical_status varchar(200), tmp_uuid_2 text, inspireid text, _node_number int8,PrimaryKey, _relationships{}_de9im text, _relationships{}_pass{} text, _nb_of_suppliers int8

Bookmark: Select skeletons which intersect boundary points
SpatialFilter_3
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> LineCombiner_2

Bookmark: Delete skeletons which intersect only 1 or 2 initial boundary line
SpatialRelator
    AGGREGATE_HANDLING = Yes
    CALC_CARD = No
    CURVE_BOUNDARY_RULE_PARAM = Default Rule
    LIST_NAME = _relationships
    PREDICATES = INTERSECTS TOUCHES
    SUCCESS_ATTR = _nb_of_suppliers
    -> Tester
Tester
    BOOL_OP = COMPOSITE
    COMPOSITE_TEST = 1 AND 2
    TEST_CLAUSE:
      TEST @Value(_nb_of_suppliers) > 0
      TEST @Value(_nb_of_suppliers) <= 2
    TEST_MODE = TEST
    FAILED -> LineCombiner_2

Bookmark: Step 1.2 (manual): correct output
Note: Manually delete lines which are not part of the BE#NL boundary

Bookmark: Step 2.2 (manual): clean polygons
Note: Manually delete polygons corresponding to enclaves

Bookmark: Step 4.2 (manual): Delete irrelevant lines
Note: Manually correct the data by going through the suspicious nodes
